(command "netload" "D:\\Daten\\Programmierung\\Tools\\diverse\\ProFilePlotten\\RNK\\MxLib.dll")
(command "netload" "D:\\Daten\\Programmierung\\Tools\\diverse\\ProFilePlotten\\RNK\\AcadLibCs.dll")
(command "netload" "D:\\Daten\\Programmierung\\Tools\\diverse\\ProFilePlotten\\Utils\\bin\\Debug\\Utils.dll")
